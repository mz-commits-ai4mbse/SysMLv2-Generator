package MainModel {
    public import '01_Stakeholder::01_Requirements::00_RequirementDefinitions'::*;
    public import '01_Stakeholder::01_Requirements::01_UserNeeds'::*;
    public import '01_Stakeholder::01_Requirements::02_StakeholderRequirements'::*; // <--- Neu hinzufügen
    public import '01_Stakeholder::00_Stakeholders'::*;
}
