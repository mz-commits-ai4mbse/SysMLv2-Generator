package J5_Satisfies_Endpoint_Syntax_Fixture {
    requirement IME_000001 {
        doc /* Engineering name: Example Requirement */
    }

    part IME_000002 {
        doc /* Engineering name: Example Structural Satisfier */
    }

    action IME_000003 {
        doc /* Engineering name: Example Functional Satisfier */
    }

    satisfy IME_000001 by IME_000002;
    satisfy IME_000001 by IME_000003;
}
