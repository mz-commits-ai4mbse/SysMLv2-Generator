package J1_UseCase_Syntax_Fixture {
    part def ExampleSystem;

    use case def ExampleUseCase {
        subject exampleSystem : ExampleSystem;

        objective {
            doc /* Demonstrate the minimal use-case-definition syntax required by Phase J. */
        }
    }
}
