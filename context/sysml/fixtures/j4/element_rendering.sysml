package J4_Element_Rendering_Syntax_Fixture {
    requirement IME_000001 {
        doc /* Engineering name: Example Requirement
Description:
The example requirement shall demonstrate J4 rendering. */
    }

    action IME_000002 {
        doc /* Engineering name: Example Function
Description:
Demonstrate deterministic action-usage rendering. */
    }

    part IME_000003 {
        doc /* Engineering name: Example Component
Description:
Demonstrate deterministic part-usage rendering. */
    }

    use case def IME_000004 {
        doc /* Engineering name: Example Use Case
Description:
Demonstrate deterministic use-case-definition rendering. */
    }
}
